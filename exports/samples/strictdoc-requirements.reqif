# Documentation export by StrictDoc

# Specification: Требования заинтересованных сторон

## STK-001: Отображение состояния насосов
Система должна предоставлять оператору актуальное состояние каждого насоса насосной станции.
- TYPE: Stakeholder
- STATUS: Approved
- PRIORITY: High
- VERIFICATION_METHOD: Demonstration
- OWNER: Владелец продукта
- SOURCE: ТЗ пилота, раздел 8
- TAGS: насосы, состояние, оператор
- RATIONALE: Оператору необходима единая и однозначная картина работы оборудования для своевременного реагирования на отклонения.
- ACCEPTANCE_CRITERIA: В демонстрационном сценарии состояние каждого подключённого насоса отображается как «работает», «остановлен», «авария» или «нет связи» и соответствует входной телеметрии.
- NOTES: Базовое пользовательское требование версии v1.

## STK-002: Предупреждение о превышении давления
Система должна предупреждать оператора о превышении допустимого порога давления.
- TYPE: Stakeholder
- STATUS: Approved
- PRIORITY: Critical
- VERIFICATION_METHOD: Demonstration
- OWNER: Владелец продукта
- SOURCE: ТЗ пилота, раздел 8
- TAGS: давление, авария, оператор
- RATIONALE: Своевременное предупреждение снижает риск повреждения оборудования и опасного режима работы насосной станции.
- ACCEPTANCE_CRITERIA: При подаче достоверного значения давления выше настроенного порога интерфейс показывает явное аварийное предупреждение с идентификатором контролируемого канала.
- NOTES: Базовое пользовательское требование версии v1.

## STK-003: Просмотр истории событий
Система должна позволять инженеру эксплуатации просматривать историю событий насосной станции.
- TYPE: Stakeholder
- STATUS: Approved
- PRIORITY: Medium
- VERIFICATION_METHOD: Demonstration
- OWNER: Инженер эксплуатации
- SOURCE: ТЗ пилота, раздел 8
- TAGS: журнал, история, события
- RATIONALE: История событий необходима для анализа причин отказов, подтверждения действий оператора и планирования обслуживания.
- ACCEPTANCE_CRITERIA: Пользователь открывает журнал и видит сохранённые события с типом, источником и временной меткой в порядке от новых к старым.
- NOTES: Базовое пользовательское требование версии v1.

# Specification: Системные требования

## SYS-001: Обновление состояния не позднее 2 секунд
Система должна обновлять отображаемое состояние насоса не позднее чем через 2 секунды после получения соответствующей телеметрии.
- TYPE: System
- STATUS: Approved
- PRIORITY: High
- VERIFICATION_METHOD: Test
- OWNER: Системный инженер
- SOURCE: ТЗ пилота, раздел 8
- TAGS: состояние, задержка, HMI
- RATIONALE: Задержка не более 2 секунд обеспечивает оператору достаточно актуальное представление о процессе и ограничивает время реакции на изменение режима.
- ACCEPTANCE_CRITERIA: Для 100 последовательных изменений телеметрии время от приёма сообщения до обновления состояния на HMI не превышает 2,0 секунды ни в одном измерении.
- NOTES: Базовое системное требование версии v1.
- Refines -> STK-001

## SYS-002: Формирование аварии при превышении порога
Система должна формировать аварию давления, когда достоверное измеренное значение давления превышает настроенный аварийный порог, и применять гистерезис 0.2 bar: после подтверждения аварии повторное срабатывание разрешается только после снижения давления до значения не выше порога минус 0.2 bar и нового превышения порога.
- TYPE: System
- STATUS: Approved
- PRIORITY: Critical
- VERIFICATION_METHOD: Test
- OWNER: Системный инженер
- SOURCE: ТЗ пилота, раздел 8
- TAGS: давление, порог, авария
- RATIONALE: Автоматическое сравнение с настраиваемым порогом необходимо для единообразного и своевременного обнаружения опасного давления.
- ACCEPTANCE_CRITERIA: В каждом из 20 независимых испытаний значение выше настроенного порога формирует аварию, а значение, равное порогу или ниже него, не формирует новую аварию. После срабатывания и подтверждения колебания давления выше порога минус 0.2 bar и не выше порога не вызывают повторную аварию; после снижения до порога минус 0.2 bar или ниже и последующего превышения порога новая авария формируется.
- NOTES: Версия v2 содержит гистерезис 0.2 bar; числовое значение является явно зафиксированным пилотным допущением.
- Refines -> STK-002

## SYS-003: Сохранение аварии до подтверждения
Система должна сохранять активный признак аварии давления до явного подтверждения оператором, даже если измеренное давление вернулось в допустимый диапазон.
- TYPE: System
- STATUS: Approved
- PRIORITY: Critical
- VERIFICATION_METHOD: Test
- OWNER: Системный инженер
- SOURCE: ТЗ пилота, раздел 8
- TAGS: авария, подтверждение, фиксация
- RATIONALE: Фиксация события предотвращает потерю информации о кратковременной опасной ситуации до того, как оператор её заметит и подтвердит.
- ACCEPTANCE_CRITERIA: После формирования аварии возврат давления в допустимый диапазон не снимает признак аварии; признак снимается только после команды подтверждения при допустимом давлении.
- NOTES: Базовое системное требование версии v1.
- Refines -> STK-002

## SYS-004: Хранение журнала не менее 30 суток
Система должна хранить журнал событий насосной станции не менее 30 календарных суток.
- TYPE: System
- STATUS: Approved
- PRIORITY: Medium
- VERIFICATION_METHOD: Analysis
- OWNER: Системный инженер
- SOURCE: ТЗ пилота, раздел 8
- TAGS: журнал, хранение, история
- RATIONALE: Тридцатисуточный интервал позволяет расследовать инциденты и анализировать поведение оборудования между плановыми циклами обслуживания.
- ACCEPTANCE_CRITERIA: Расчёт ёмкости и проверка тестовой временной шкалой подтверждают доступность всех событий за последние 30 суток при расчётной максимальной интенсивности 10 000 событий в сутки.
- NOTES: В v2 статус изменён с Review на Approved по сценарию Diff/Merge.
- Refines -> STK-003

## SYS-005: Обнаружение потери связи не позднее 3 секунд
Система должна обнаруживать потерю связи с источником телеметрии не позднее чем через 3 секунды после последнего корректного сообщения.
- TYPE: System
- STATUS: Approved
- PRIORITY: Critical
- VERIFICATION_METHOD: Test
- OWNER: Системный инженер
- SOURCE: ТЗ пилота, раздел 8
- TAGS: связь, диагностика, задержка
- RATIONALE: Быстрое обнаружение отсутствия данных не позволяет оператору принимать устаревшее состояние насоса за актуальное.
- ACCEPTANCE_CRITERIA: В 20 испытаниях с прекращением потока телеметрии признак потери связи устанавливается не позднее чем через 3,0 секунды после последнего принятого корректного сообщения.
- NOTES: Базовое системное требование версии v1.
- Refines -> STK-001

## SYS-006: Отображение признака устаревших данных
Система должна отображать на HMI явный признак устаревших данных при установленном признаке потери связи с источником телеметрии и сохранять его до получения нового корректного сообщения.
- TYPE: System
- STATUS: Approved
- PRIORITY: High
- VERIFICATION_METHOD: Test
- OWNER: Системный инженер
- SOURCE: ТЗ пилота, раздел 13
- TAGS: HMI, устаревшие-данные, связь
- RATIONALE: Явная индикация не позволяет оператору принять последнее полученное состояние насоса за актуальное после прекращения телеметрии.
- ACCEPTANCE_CRITERIA: В каждом из 20 испытаний после фиксации потери связи признак устаревших данных появляется на HMI не позднее 2,0 секунды, остаётся видимым в течение 10 последовательных циклов без корректной телеметрии и исчезает не позднее 2,0 секунды после первого нового корректного сообщения.
- NOTES: Добавлено в v2; Refines -> STK-001 является допущением, зафиксированным в CHANGE_SCENARIO.md.
- Refines -> STK-001

# Specification: Программные и интерфейсные требования

## IF-001: Приём телеметрии по Modbus TCP
Система должна принимать значения состояния насосов и давления от шлюза датчиков по протоколу Modbus TCP.
- TYPE: Interface
- STATUS: Approved
- PRIORITY: High
- VERIFICATION_METHOD: Test
- OWNER: Инженер интеграции
- SOURCE: ТЗ пилота, раздел 8
- TAGS: Modbus-TCP, телеметрия, интерфейс
- RATIONALE: Modbus TCP является заданным интерфейсом получения исходных данных о состоянии насосной станции для демонстрационного объекта.
- ACCEPTANCE_CRITERIA: При подключении эмулятора Modbus TCP система без ошибок принимает 10 000 последовательных наборов регистров состояния и давления и передаёт их на обработку.
- NOTES: Базовое интерфейсное требование версии v1.
- Derives -> SYS-001
- Derives -> SYS-002

## IF-002: Синхронизация времени по NTP
Система должна синхронизировать системное время с настроенным сервером NTP.
- TYPE: Interface
- STATUS: Approved
- PRIORITY: Medium
- VERIFICATION_METHOD: Test
- OWNER: Инженер интеграции
- SOURCE: ТЗ пилота, раздел 8
- TAGS: NTP, время, интерфейс
- RATIONALE: Единая временная база необходима для сопоставления событий станции с данными других систем и для достоверной последовательности журнала.
- ACCEPTANCE_CRITERIA: После установления связи с NTP-сервером абсолютное расхождение системного времени с эталоном не превышает 100 миллисекунд в течение 24 часов испытания.
- NOTES: Базовое интерфейсное требование версии v1.
- Derives -> SYS-004

## SW-001: Опрос телеметрии каждые 500 мс
Программное обеспечение должно инициировать опрос телеметрии с периодом 500 миллисекунд.
- TYPE: Software
- STATUS: Approved
- PRIORITY: High
- VERIFICATION_METHOD: Test
- OWNER: Ведущий разработчик
- SOURCE: ТЗ пилота, раздел 8
- TAGS: опрос, телеметрия, период
- RATIONALE: Период 500 миллисекунд оставляет запас времени на передачу и обработку данных для выполнения системного ограничения обновления в 2 секунды.
- ACCEPTANCE_CRITERIA: Для 1 000 последовательных циклов средний период опроса составляет 500 миллисекунд, а ни один измеренный период не превышает 600 миллисекунд.
- NOTES: Базовое программное требование версии v1.
- Derives -> SYS-001

## SW-002: Сравнение давления с порогом
Программное обеспечение должно сравнивать каждое принятое достоверное значение давления с текущим настроенным аварийным порогом.
- TYPE: Software
- STATUS: Approved
- PRIORITY: Critical
- VERIFICATION_METHOD: Test
- OWNER: Ведущий разработчик
- SOURCE: ТЗ пилота, раздел 8
- TAGS: давление, сравнение, порог
- RATIONALE: Обработка каждого значения предотвращает пропуск кратковременного превышения между циклами обновления интерфейса.
- ACCEPTANCE_CRITERIA: Модуль сравнения правильно классифицирует все граничные значения из набора: ниже порога, равно порогу и выше порога на минимальный шаг входного регистра.
- NOTES: Базовое программное требование версии v1.
- Derives -> SYS-002

## SW-003: Автомат состояний аварии
Программное обеспечение должно реализовать автомат состояний аварии с состояниями «норма», «активна неподтверждённая» и «активна подтверждённая».
- TYPE: Software
- STATUS: Approved
- PRIORITY: Critical
- VERIFICATION_METHOD: Test
- OWNER: Ведущий разработчик
- SOURCE: ТЗ пилота, раздел 8
- TAGS: автомат-состояний, авария, подтверждение
- RATIONALE: Явный автомат состояний делает правила фиксации и подтверждения аварии детерминированными и проверяемыми.
- ACCEPTANCE_CRITERIA: Автомат проходит все допустимые переходы по таблице состояний, отвергает недопустимые переходы и после перезапуска восстанавливает последнее зафиксированное аварийное состояние.
- NOTES: Базовое программное требование версии v1.
- Derives -> SYS-003

## SW-004: Запись события с меткой UTC
Программное обеспечение должно сохранять каждое событие журнала с временной меткой в UTC.
- TYPE: Software
- STATUS: Approved
- PRIORITY: Medium
- VERIFICATION_METHOD: Test
- OWNER: Ведущий разработчик
- SOURCE: ТЗ пилота, раздел 8
- TAGS: журнал, UTC, событие
- RATIONALE: UTC исключает неоднозначность часовых поясов и переходов времени при сравнении записей из разных источников.
- ACCEPTANCE_CRITERIA: Для 1 000 сформированных событий каждая запись содержит синтаксически корректную метку UTC, а последовательность меток не убывает.
- NOTES: Требование зависит от доступности синхронизированного времени.
- Derives -> SYS-004
- DependsOn -> IF-002

# Specification: Требования безопасности

## SAF-001: Недостоверные данные не снимают аварию
Система не должна снимать зафиксированную аварию на основании значения давления, помеченного как недостоверное.
- TYPE: Safety
- STATUS: Approved
- PRIORITY: Critical
- VERIFICATION_METHOD: Test
- OWNER: Инженер по безопасности
- SOURCE: ТЗ пилота, раздел 8
- TAGS: безопасность, качество-данных, авария
- RATIONALE: Использование недостоверных данных для снятия аварии способно скрыть сохраняющуюся опасную ситуацию и создать ложное представление о нормальном режиме.
- ACCEPTANCE_CRITERIA: Во всех испытаниях с активной аварией поступление значений с признаком недостоверности не изменяет состояние аварии независимо от численного значения давления.
- NOTES: Базовое требование безопасности версии v1.
- Derives -> SYS-003
- Derives -> SYS-005

## SAF-002: Потеря связи формирует фиксируемую аварию
Система должна формировать фиксируемую аварию при обнаружении потери связи с источником телеметрии.
- TYPE: Safety
- STATUS: Approved
- PRIORITY: Critical
- VERIFICATION_METHOD: Test
- OWNER: Инженер по безопасности
- SOURCE: ТЗ пилота, раздел 8
- TAGS: безопасность, потеря-связи, фиксация
- RATIONALE: Потеря наблюдаемости контролируемого процесса является самостоятельным опасным событием и должна оставаться заметной до реакции оператора.
- ACCEPTANCE_CRITERIA: В каждом из 20 испытаний потеря связи переводит систему в аварийное состояние, которое не снимается восстановлением связи без явного подтверждения оператором.
- NOTES: Базовое требование безопасности версии v1.
- Derives -> SYS-005

# Specification: Проверка и испытания

## TST-001: Проверка задержки отображения
Подать 100 изменений состояния насоса с зарегистрированным временем приёма и измерить время появления каждого нового состояния на HMI.
- TYPE: TestCase
- STATUS: Approved
- PRIORITY: High
- VERIFICATION_METHOD: Test
- OWNER: Инженер по испытаниям
- SOURCE: ТЗ пилота, раздел 8
- TAGS: тест, задержка, HMI
- RATIONALE: Испытание непосредственно измеряет сквозную задержку от входной телеметрии до отображения.
- ACCEPTANCE_CRITERIA: Все 100 измеренных задержек не превышают 2,0 секунды; для каждого измерения сохранены входная и выходная временные метки.
- NOTES: Позитивный тест производительности версии v1.
- Verifies -> SYS-001

## TST-002: Проверка аварийного порога
Настроить аварийный порог и последовательно подать значения ниже порога, равное порогу и выше порога. После срабатывания подтвердить аварию, изменять давление в диапазоне между порогом и порогом минус 0.2 bar, затем снизить его до порога минус 0.2 bar и снова превысить порог.
- TYPE: TestCase
- STATUS: Approved
- PRIORITY: Critical
- VERIFICATION_METHOD: Test
- OWNER: Инженер по испытаниям
- SOURCE: ТЗ пилота, раздел 8
- TAGS: тест, давление, порог
- RATIONALE: Набор граничных значений выявляет ошибки сравнения и подтверждает как правило формирования аварии, так и гистерезис, добавленный в SYS-002 версии v2.
- ACCEPTANCE_CRITERIA: Авария не формируется для исходного значения ниже или равного порогу и формируется для каждого достоверного значения выше порога. После подтверждения значения выше порога минус 0.2 bar не вызывают повторную аварию; после снижения до порога минус 0.2 bar или ниже следующее превышение порога формирует новую аварию.
- NOTES: В v2 тест дополнен сценарием гистерезиса SYS-002 без изменения UID и MID.
- Verifies -> SYS-002

## TST-003: Проверка подтверждения аварии
Сформировать аварию, вернуть давление в допустимый диапазон, подать недостоверные данные и затем выполнить явное подтверждение оператором.
- TYPE: TestCase
- STATUS: Approved
- PRIORITY: Critical
- VERIFICATION_METHOD: Test
- OWNER: Инженер по испытаниям
- SOURCE: ТЗ пилота, раздел 8
- TAGS: тест, авария, подтверждение
- RATIONALE: Последовательность проверяет фиксацию аварии, защиту от недостоверных данных и допустимое условие снятия одним сквозным сценарием.
- ACCEPTANCE_CRITERIA: Авария сохраняется после нормализации давления и поступления недостоверных данных и снимается только после команды подтверждения при достоверном допустимом давлении.
- NOTES: Проверяет системное требование и связанное требование безопасности.
- Verifies -> SYS-003
- Verifies -> SAF-001

## TST-004: Проверка хранения журнала
Заполнить журнал событиями расчётной максимальной интенсивности, сдвинуть тестовую временную шкалу на 30 суток и проверить доступность событий на границе периода хранения.
- TYPE: TestCase
- STATUS: Review
- PRIORITY: Medium
- VERIFICATION_METHOD: Analysis
- OWNER: Инженер по испытаниям
- SOURCE: ТЗ пилота, раздел 8
- TAGS: проверка, журнал, хранение
- RATIONALE: Комбинация анализа ёмкости и управляемой временной шкалы позволяет проверить длительный период без ожидания 30 календарных суток.
- ACCEPTANCE_CRITERIA: Все события с возрастом до 30 суток доступны для просмотра; удаление более старых событий не затрагивает записи внутри обязательного периода.
- NOTES: Метод Analysis согласован со статусом Review требования SYS-004.
- Verifies -> SYS-004

## TST-005: Проверка потери связи
Прекратить передачу телеметрии, измерить время обнаружения потери связи, восстановить передачу и проверить поведение фиксируемой аварии.
- TYPE: TestCase
- STATUS: Approved
- PRIORITY: Critical
- VERIFICATION_METHOD: Test
- OWNER: Инженер по испытаниям
- SOURCE: ТЗ пилота, раздел 8
- TAGS: тест, потеря-связи, авария
- RATIONALE: Сквозное испытание одновременно подтверждает временное ограничение диагностики и безопасное фиксирование события потери связи.
- ACCEPTANCE_CRITERIA: Потеря связи обнаруживается не позднее 3,0 секунды, авария формируется и сохраняется после восстановления передачи до явного подтверждения оператором.
- NOTES: Проверяет SYS-005 и SAF-002.
- Verifies -> SYS-005
- Verifies -> SAF-002

## TST-006: Проверка временных меток
Подключить контролируемый NTP-сервер, сформировать 1 000 событий и сравнить сохранённые временные метки UTC с эталонным временем.
- TYPE: TestCase
- STATUS: Approved
- PRIORITY: Medium
- VERIFICATION_METHOD: Test
- OWNER: Инженер по испытаниям
- SOURCE: ТЗ пилота, раздел 8
- TAGS: тест, UTC, NTP
- RATIONALE: Испытание проверяет как точность синхронизации интерфейса, так и корректное использование этого времени при записи событий.
- ACCEPTANCE_CRITERIA: Расхождение с эталоном не превышает 100 миллисекунд, каждая метка имеет формат UTC и последовательность меток не убывает.
- NOTES: Проверяет SW-004 и IF-002.
- Verifies -> SW-004
- Verifies -> IF-002

## TST-007: Проверка признака устаревших данных
В 20 испытаниях прекратить поток телеметрии, дождаться фиксации потери связи, наблюдать признак устаревших данных на HMI в течение 10 циклов обновления и затем восстановить передачу корректных сообщений.
- TYPE: TestCase
- STATUS: Approved
- PRIORITY: High
- VERIFICATION_METHOD: Test
- OWNER: Инженер по испытаниям
- SOURCE: ТЗ пилота, раздел 13
- TAGS: тест, устаревшие-данные, HMI
- RATIONALE: Испытание проверяет появление, удержание и снятие признака устаревших данных во всём сценарии потери и восстановления связи.
- ACCEPTANCE_CRITERIA: Во всех 20 испытаниях признак появляется не позднее 2,0 секунды после фиксации потери связи, остаётся видимым во всех 10 циклах без корректной телеметрии и исчезает не позднее 2,0 секунды после первого нового корректного сообщения.
- NOTES: Добавлено в v2 для проверки SYS-006.
- Verifies -> SYS-006
