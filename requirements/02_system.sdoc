[DOCUMENT]
MID: mid_doc_system
TITLE: Системные требования
VERSION: 1.0
DATE: 2026-09-01
OPTIONS:
  ENABLE_MID: True

[GRAMMAR]
IMPORT_FROM_FILE: grammar.sgra

[REQUIREMENT]
MID: mid_req_sys_001
UID: SYS-001
TYPE: System
STATUS: Approved
PRIORITY: High
VERIFICATION_METHOD: Test
OWNER: Системный инженер
SOURCE: ТЗ пилота, раздел 8
TAGS: состояние, задержка, HMI
TITLE: Обновление состояния не позднее 2 секунд
STATEMENT: >>>
Система должна обновлять отображаемое состояние насоса не позднее чем через 2 секунды
после получения соответствующей телеметрии.
<<<
RATIONALE: >>>
Задержка не более 2 секунд обеспечивает оператору достаточно актуальное представление о
процессе и ограничивает время реакции на изменение режима.
<<<
ACCEPTANCE_CRITERIA: >>>
Для 100 последовательных изменений телеметрии время от приёма сообщения до обновления
состояния на HMI не превышает 2,0 секунды ни в одном измерении.
<<<
COMMENT: Базовое системное требование версии v1.
RELATIONS:
- TYPE: Parent
  VALUE: STK-001
  ROLE: Refines

[REQUIREMENT]
MID: mid_req_sys_002
UID: SYS-002
TYPE: System
STATUS: Approved
PRIORITY: Critical
VERIFICATION_METHOD: Test
OWNER: Системный инженер
SOURCE: ТЗ пилота, раздел 8
TAGS: давление, порог, авария
TITLE: Формирование аварии при превышении порога
STATEMENT: >>>
Система должна формировать аварию давления, когда достоверное измеренное значение
давления превышает настроенный аварийный порог, и применять гистерезис 0.2 bar:
после подтверждения аварии повторное срабатывание разрешается только после снижения
давления до значения не выше порога минус 0.2 bar и нового превышения порога.
<<<
RATIONALE: >>>
Автоматическое сравнение с настраиваемым порогом необходимо для единообразного и
своевременного обнаружения опасного давления.
<<<
ACCEPTANCE_CRITERIA: >>>
В каждом из 20 независимых испытаний значение выше настроенного порога формирует
аварию, а значение, равное порогу или ниже него, не формирует новую аварию.
После срабатывания и подтверждения колебания давления выше порога минус 0.2 bar и
не выше порога не вызывают повторную аварию; после снижения до порога минус
0.2 bar или ниже и последующего превышения порога новая авария формируется.
<<<
COMMENT: Версия v2 содержит гистерезис 0.2 bar; числовое значение является явно зафиксированным пилотным допущением.
RELATIONS:
- TYPE: Parent
  VALUE: STK-002
  ROLE: Refines

[REQUIREMENT]
MID: mid_req_sys_003
UID: SYS-003
TYPE: System
STATUS: Approved
PRIORITY: Critical
VERIFICATION_METHOD: Test
OWNER: Системный инженер
SOURCE: ТЗ пилота, раздел 8
TAGS: авария, подтверждение, фиксация
TITLE: Сохранение аварии до подтверждения
STATEMENT: >>>
Система должна сохранять активный признак аварии давления до явного подтверждения
оператором, даже если измеренное давление вернулось в допустимый диапазон.
<<<
RATIONALE: >>>
Фиксация события предотвращает потерю информации о кратковременной опасной ситуации до
того, как оператор её заметит и подтвердит.
<<<
ACCEPTANCE_CRITERIA: >>>
После формирования аварии возврат давления в допустимый диапазон не снимает признак
аварии; признак снимается только после команды подтверждения при допустимом давлении.
<<<
COMMENT: Базовое системное требование версии v1.
RELATIONS:
- TYPE: Parent
  VALUE: STK-002
  ROLE: Refines

[REQUIREMENT]
MID: mid_req_sys_004
UID: SYS-004
TYPE: System
STATUS: Approved
PRIORITY: Medium
VERIFICATION_METHOD: Analysis
OWNER: Системный инженер
SOURCE: ТЗ пилота, раздел 8
TAGS: журнал, хранение, история
TITLE: Хранение журнала не менее 30 суток
STATEMENT: >>>
Система должна хранить журнал событий насосной станции не менее 30 календарных суток.
<<<
RATIONALE: >>>
Тридцатисуточный интервал позволяет расследовать инциденты и анализировать поведение
оборудования между плановыми циклами обслуживания.
<<<
ACCEPTANCE_CRITERIA: >>>
Расчёт ёмкости и проверка тестовой временной шкалой подтверждают доступность всех событий
за последние 30 суток при расчётной максимальной интенсивности 10 000 событий в сутки.
<<<
COMMENT: В v2 статус изменён с Review на Approved по сценарию Diff/Merge.
RELATIONS:
- TYPE: Parent
  VALUE: STK-003
  ROLE: Refines

[REQUIREMENT]
MID: mid_req_sys_005
UID: SYS-005
TYPE: System
STATUS: Approved
PRIORITY: Critical
VERIFICATION_METHOD: Test
OWNER: Системный инженер
SOURCE: ТЗ пилота, раздел 8
TAGS: связь, диагностика, задержка
TITLE: Обнаружение потери связи не позднее 3 секунд
STATEMENT: >>>
Система должна обнаруживать потерю связи с источником телеметрии не позднее чем через 3
секунды после последнего корректного сообщения.
<<<
RATIONALE: >>>
Быстрое обнаружение отсутствия данных не позволяет оператору принимать устаревшее
состояние насоса за актуальное.
<<<
ACCEPTANCE_CRITERIA: >>>
В 20 испытаниях с прекращением потока телеметрии признак потери связи устанавливается не
позднее чем через 3,0 секунды после последнего принятого корректного сообщения.
<<<
COMMENT: Базовое системное требование версии v1.
RELATIONS:
- TYPE: Parent
  VALUE: STK-001
  ROLE: Refines

[REQUIREMENT]
MID: mid_req_sys_006
UID: SYS-006
TYPE: System
STATUS: Approved
PRIORITY: High
VERIFICATION_METHOD: Test
OWNER: Системный инженер
SOURCE: ТЗ пилота, раздел 13
TAGS: HMI, устаревшие-данные, связь
TITLE: Отображение признака устаревших данных
STATEMENT: >>>
Система должна отображать на HMI явный признак устаревших данных при установленном
признаке потери связи с источником телеметрии и сохранять его до получения нового
корректного сообщения.
<<<
RATIONALE: >>>
Явная индикация не позволяет оператору принять последнее полученное состояние насоса
за актуальное после прекращения телеметрии.
<<<
ACCEPTANCE_CRITERIA: >>>
В каждом из 20 испытаний после фиксации потери связи признак устаревших данных
появляется на HMI не позднее 2,0 секунды, остаётся видимым в течение 10
последовательных циклов без корректной телеметрии и исчезает не позднее 2,0 секунды
после первого нового корректного сообщения.
<<<
COMMENT: Добавлено в v2; Refines -> STK-001 является допущением, зафиксированным в CHANGE_SCENARIO.md.
RELATIONS:
- TYPE: Parent
  VALUE: STK-001
  ROLE: Refines
