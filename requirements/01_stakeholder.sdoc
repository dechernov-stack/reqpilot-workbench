[DOCUMENT]
MID: mid_doc_stakeholder
TITLE: Требования заинтересованных сторон
VERSION: 1.0
DATE: 2026-09-01
OPTIONS:
  ENABLE_MID: True

[GRAMMAR]
IMPORT_FROM_FILE: grammar.sgra

[REQUIREMENT]
MID: mid_req_stk_001
UID: STK-001
TYPE: Stakeholder
STATUS: Approved
PRIORITY: High
VERIFICATION_METHOD: Demonstration
OWNER: Владелец продукта
SOURCE: ТЗ пилота, раздел 8
TAGS: насосы, состояние, оператор
TITLE: Отображение состояния насосов
STATEMENT: >>>
Система должна предоставлять оператору актуальное состояние каждого насоса насосной
станции.
<<<
RATIONALE: >>>
Оператору необходима единая и однозначная картина работы оборудования для своевременного
реагирования на отклонения.
<<<
ACCEPTANCE_CRITERIA: >>>
В демонстрационном сценарии состояние каждого подключённого насоса отображается как
«работает», «остановлен», «авария» или «нет связи» и соответствует входной телеметрии.
<<<
COMMENT: Базовое пользовательское требование версии v1.

[REQUIREMENT]
MID: mid_req_stk_002
UID: STK-002
TYPE: Stakeholder
STATUS: Approved
PRIORITY: Critical
VERIFICATION_METHOD: Demonstration
OWNER: Владелец продукта
SOURCE: ТЗ пилота, раздел 8
TAGS: давление, авария, оператор
TITLE: Предупреждение о превышении давления
STATEMENT: >>>
Система должна предупреждать оператора о превышении допустимого порога давления.
<<<
RATIONALE: >>>
Своевременное предупреждение снижает риск повреждения оборудования и опасного режима
работы насосной станции.
<<<
ACCEPTANCE_CRITERIA: >>>
При подаче достоверного значения давления выше настроенного порога интерфейс показывает
явное аварийное предупреждение с идентификатором контролируемого канала.
<<<
COMMENT: Базовое пользовательское требование версии v1.

[REQUIREMENT]
MID: mid_req_stk_003
UID: STK-003
TYPE: Stakeholder
STATUS: Approved
PRIORITY: Medium
VERIFICATION_METHOD: Demonstration
OWNER: Инженер эксплуатации
SOURCE: ТЗ пилота, раздел 8
TAGS: журнал, история, события
TITLE: Просмотр истории событий
STATEMENT: >>>
Система должна позволять инженеру эксплуатации просматривать историю событий насосной
станции.
<<<
RATIONALE: >>>
История событий необходима для анализа причин отказов, подтверждения действий оператора и
планирования обслуживания.
<<<
ACCEPTANCE_CRITERIA: >>>
Пользователь открывает журнал и видит сохранённые события с типом, источником и временной
меткой в порядке от новых к старым.
<<<
COMMENT: Базовое пользовательское требование версии v1.
