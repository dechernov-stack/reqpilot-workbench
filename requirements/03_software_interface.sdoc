[DOCUMENT]
MID: mid_doc_software_interface
TITLE: Программные и интерфейсные требования
VERSION: 1.0
DATE: 2026-09-01
OPTIONS:
  ENABLE_MID: True

[GRAMMAR]
IMPORT_FROM_FILE: grammar.sgra

[REQUIREMENT]
MID: mid_req_if_001
UID: IF-001
TYPE: Interface
STATUS: Approved
PRIORITY: High
VERIFICATION_METHOD: Test
OWNER: Инженер интеграции
SOURCE: ТЗ пилота, раздел 8
TAGS: Modbus-TCP, телеметрия, интерфейс
TITLE: Приём телеметрии по Modbus TCP
STATEMENT: >>>
Система должна принимать значения состояния насосов и давления от шлюза датчиков по
протоколу Modbus TCP.
<<<
RATIONALE: >>>
Modbus TCP является заданным интерфейсом получения исходных данных о состоянии насосной
станции для демонстрационного объекта.
<<<
ACCEPTANCE_CRITERIA: >>>
При подключении эмулятора Modbus TCP система без ошибок принимает 10 000 последовательных
наборов регистров состояния и давления и передаёт их на обработку.
<<<
COMMENT: Базовое интерфейсное требование версии v1.
RELATIONS:
- TYPE: Parent
  VALUE: SYS-001
  ROLE: Derives
- TYPE: Parent
  VALUE: SYS-002
  ROLE: Derives

[REQUIREMENT]
MID: mid_req_if_002
UID: IF-002
TYPE: Interface
STATUS: Approved
PRIORITY: Medium
VERIFICATION_METHOD: Test
OWNER: Инженер интеграции
SOURCE: ТЗ пилота, раздел 8
TAGS: NTP, время, интерфейс
TITLE: Синхронизация времени по NTP
STATEMENT: >>>
Система должна синхронизировать системное время с настроенным сервером NTP.
<<<
RATIONALE: >>>
Единая временная база необходима для сопоставления событий станции с данными других
систем и для достоверной последовательности журнала.
<<<
ACCEPTANCE_CRITERIA: >>>
После установления связи с NTP-сервером абсолютное расхождение системного времени с
эталоном не превышает 100 миллисекунд в течение 24 часов испытания.
<<<
COMMENT: Базовое интерфейсное требование версии v1.
RELATIONS:
- TYPE: Parent
  VALUE: SYS-004
  ROLE: Derives

[REQUIREMENT]
MID: mid_req_sw_001
UID: SW-001
TYPE: Software
STATUS: Approved
PRIORITY: High
VERIFICATION_METHOD: Test
OWNER: Ведущий разработчик
SOURCE: ТЗ пилота, раздел 8
TAGS: опрос, телеметрия, период
TITLE: Опрос телеметрии каждые 500 мс
STATEMENT: >>>
Программное обеспечение должно инициировать опрос телеметрии с периодом 500 миллисекунд.
<<<
RATIONALE: >>>
Период 500 миллисекунд оставляет запас времени на передачу и обработку данных для
выполнения системного ограничения обновления в 2 секунды.
<<<
ACCEPTANCE_CRITERIA: >>>
Для 1 000 последовательных циклов средний период опроса составляет 500 миллисекунд, а
ни один измеренный период не превышает 600 миллисекунд.
<<<
COMMENT: Базовое программное требование версии v1.
RELATIONS:
- TYPE: Parent
  VALUE: SYS-001
  ROLE: Derives

[REQUIREMENT]
MID: mid_req_sw_002
UID: SW-002
TYPE: Software
STATUS: Approved
PRIORITY: Critical
VERIFICATION_METHOD: Test
OWNER: Ведущий разработчик
SOURCE: ТЗ пилота, раздел 8
TAGS: давление, сравнение, порог
TITLE: Сравнение давления с порогом
STATEMENT: >>>
Программное обеспечение должно сравнивать каждое принятое достоверное значение давления
с текущим настроенным аварийным порогом.
<<<
RATIONALE: >>>
Обработка каждого значения предотвращает пропуск кратковременного превышения между
циклами обновления интерфейса.
<<<
ACCEPTANCE_CRITERIA: >>>
Модуль сравнения правильно классифицирует все граничные значения из набора: ниже порога,
равно порогу и выше порога на минимальный шаг входного регистра.
<<<
COMMENT: Базовое программное требование версии v1.
RELATIONS:
- TYPE: Parent
  VALUE: SYS-002
  ROLE: Derives

[REQUIREMENT]
MID: mid_req_sw_003
UID: SW-003
TYPE: Software
STATUS: Approved
PRIORITY: Critical
VERIFICATION_METHOD: Test
OWNER: Ведущий разработчик
SOURCE: ТЗ пилота, раздел 8
TAGS: автомат-состояний, авария, подтверждение
TITLE: Автомат состояний аварии
STATEMENT: >>>
Программное обеспечение должно реализовать автомат состояний аварии с состояниями
«норма», «активна неподтверждённая» и «активна подтверждённая».
<<<
RATIONALE: >>>
Явный автомат состояний делает правила фиксации и подтверждения аварии детерминированными
и проверяемыми.
<<<
ACCEPTANCE_CRITERIA: >>>
Автомат проходит все допустимые переходы по таблице состояний, отвергает недопустимые
переходы и после перезапуска восстанавливает последнее зафиксированное аварийное состояние.
<<<
COMMENT: Базовое программное требование версии v1.
RELATIONS:
- TYPE: Parent
  VALUE: SYS-003
  ROLE: Derives

[REQUIREMENT]
MID: mid_req_sw_004
UID: SW-004
TYPE: Software
STATUS: Approved
PRIORITY: Medium
VERIFICATION_METHOD: Test
OWNER: Ведущий разработчик
SOURCE: ТЗ пилота, раздел 8
TAGS: журнал, UTC, событие
TITLE: Запись события с меткой UTC
STATEMENT: >>>
Программное обеспечение должно сохранять каждое событие журнала с временной меткой в UTC.
<<<
RATIONALE: >>>
UTC исключает неоднозначность часовых поясов и переходов времени при сравнении записей из
разных источников.
<<<
ACCEPTANCE_CRITERIA: >>>
Для 1 000 сформированных событий каждая запись содержит синтаксически корректную метку UTC,
а последовательность меток не убывает.
<<<
COMMENT: Требование зависит от доступности синхронизированного времени.
RELATIONS:
- TYPE: Parent
  VALUE: SYS-004
  ROLE: Derives
- TYPE: Parent
  VALUE: IF-002
  ROLE: DependsOn
