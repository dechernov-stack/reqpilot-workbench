[DOCUMENT]
MID: mid_doc_verification
TITLE: Проверка и испытания
VERSION: 1.0
DATE: 2026-09-01
OPTIONS:
  ENABLE_MID: True

[GRAMMAR]
IMPORT_FROM_FILE: grammar.sgra

[REQUIREMENT]
MID: mid_req_tst_001
UID: TST-001
TYPE: TestCase
STATUS: Approved
PRIORITY: High
VERIFICATION_METHOD: Test
OWNER: Инженер по испытаниям
SOURCE: ТЗ пилота, раздел 8
TAGS: тест, задержка, HMI
TITLE: Проверка задержки отображения
STATEMENT: >>>
Подать 100 изменений состояния насоса с зарегистрированным временем приёма и измерить
время появления каждого нового состояния на HMI.
<<<
RATIONALE: >>>
Испытание непосредственно измеряет сквозную задержку от входной телеметрии до отображения.
<<<
ACCEPTANCE_CRITERIA: >>>
Все 100 измеренных задержек не превышают 2,0 секунды; для каждого измерения сохранены
входная и выходная временные метки.
<<<
COMMENT: Позитивный тест производительности версии v1.
RELATIONS:
- TYPE: Parent
  VALUE: SYS-001
  ROLE: Verifies

[REQUIREMENT]
MID: mid_req_tst_002
UID: TST-002
TYPE: TestCase
STATUS: Approved
PRIORITY: Critical
VERIFICATION_METHOD: Test
OWNER: Инженер по испытаниям
SOURCE: ТЗ пилота, раздел 8
TAGS: тест, давление, порог
TITLE: Проверка аварийного порога
STATEMENT: >>>
Настроить аварийный порог и последовательно подать значения ниже порога, равное порогу и
выше порога. После срабатывания подтвердить аварию, изменять давление в диапазоне между
порогом и порогом минус 0.2 bar, затем снизить его до порога минус 0.2 bar и снова
превысить порог.
<<<
RATIONALE: >>>
Набор граничных значений выявляет ошибки сравнения и подтверждает как правило формирования
аварии, так и гистерезис, добавленный в SYS-002 версии v2.
<<<
ACCEPTANCE_CRITERIA: >>>
Авария не формируется для исходного значения ниже или равного порогу и формируется для
каждого достоверного значения выше порога. После подтверждения значения выше порога минус
0.2 bar не вызывают повторную аварию; после снижения до порога минус 0.2 bar или ниже
следующее превышение порога формирует новую аварию.
<<<
COMMENT: В v2 тест дополнен сценарием гистерезиса SYS-002 без изменения UID и MID.
RELATIONS:
- TYPE: Parent
  VALUE: SYS-002
  ROLE: Verifies

[REQUIREMENT]
MID: mid_req_tst_003
UID: TST-003
TYPE: TestCase
STATUS: Approved
PRIORITY: Critical
VERIFICATION_METHOD: Test
OWNER: Инженер по испытаниям
SOURCE: ТЗ пилота, раздел 8
TAGS: тест, авария, подтверждение
TITLE: Проверка подтверждения аварии
STATEMENT: >>>
Сформировать аварию, вернуть давление в допустимый диапазон, подать недостоверные данные и
затем выполнить явное подтверждение оператором.
<<<
RATIONALE: >>>
Последовательность проверяет фиксацию аварии, защиту от недостоверных данных и допустимое
условие снятия одним сквозным сценарием.
<<<
ACCEPTANCE_CRITERIA: >>>
Авария сохраняется после нормализации давления и поступления недостоверных данных и
снимается только после команды подтверждения при достоверном допустимом давлении.
<<<
COMMENT: Проверяет системное требование и связанное требование безопасности.
RELATIONS:
- TYPE: Parent
  VALUE: SYS-003
  ROLE: Verifies
- TYPE: Parent
  VALUE: SAF-001
  ROLE: Verifies

[REQUIREMENT]
MID: mid_req_tst_004
UID: TST-004
TYPE: TestCase
STATUS: Review
PRIORITY: Medium
VERIFICATION_METHOD: Analysis
OWNER: Инженер по испытаниям
SOURCE: ТЗ пилота, раздел 8
TAGS: проверка, журнал, хранение
TITLE: Проверка хранения журнала
STATEMENT: >>>
Заполнить журнал событиями расчётной максимальной интенсивности, сдвинуть тестовую временную
шкалу на 30 суток и проверить доступность событий на границе периода хранения.
<<<
RATIONALE: >>>
Комбинация анализа ёмкости и управляемой временной шкалы позволяет проверить длительный
период без ожидания 30 календарных суток.
<<<
ACCEPTANCE_CRITERIA: >>>
Все события с возрастом до 30 суток доступны для просмотра; удаление более старых событий
не затрагивает записи внутри обязательного периода.
<<<
COMMENT: Метод Analysis согласован со статусом Review требования SYS-004.
RELATIONS:
- TYPE: Parent
  VALUE: SYS-004
  ROLE: Verifies

[REQUIREMENT]
MID: mid_req_tst_005
UID: TST-005
TYPE: TestCase
STATUS: Approved
PRIORITY: Critical
VERIFICATION_METHOD: Test
OWNER: Инженер по испытаниям
SOURCE: ТЗ пилота, раздел 8
TAGS: тест, потеря-связи, авария
TITLE: Проверка потери связи
STATEMENT: >>>
Прекратить передачу телеметрии, измерить время обнаружения потери связи, восстановить
передачу и проверить поведение фиксируемой аварии.
<<<
RATIONALE: >>>
Сквозное испытание одновременно подтверждает временное ограничение диагностики и безопасное
фиксирование события потери связи.
<<<
ACCEPTANCE_CRITERIA: >>>
Потеря связи обнаруживается не позднее 3,0 секунды, авария формируется и сохраняется после
восстановления передачи до явного подтверждения оператором.
<<<
COMMENT: Проверяет SYS-005 и SAF-002.
RELATIONS:
- TYPE: Parent
  VALUE: SYS-005
  ROLE: Verifies
- TYPE: Parent
  VALUE: SAF-002
  ROLE: Verifies

[REQUIREMENT]
MID: mid_req_tst_006
UID: TST-006
TYPE: TestCase
STATUS: Approved
PRIORITY: Medium
VERIFICATION_METHOD: Test
OWNER: Инженер по испытаниям
SOURCE: ТЗ пилота, раздел 8
TAGS: тест, UTC, NTP
TITLE: Проверка временных меток
STATEMENT: >>>
Подключить контролируемый NTP-сервер, сформировать 1 000 событий и сравнить сохранённые
временные метки UTC с эталонным временем.
<<<
RATIONALE: >>>
Испытание проверяет как точность синхронизации интерфейса, так и корректное использование
этого времени при записи событий.
<<<
ACCEPTANCE_CRITERIA: >>>
Расхождение с эталоном не превышает 100 миллисекунд, каждая метка имеет формат UTC и
последовательность меток не убывает.
<<<
COMMENT: Проверяет SW-004 и IF-002.
RELATIONS:
- TYPE: Parent
  VALUE: SW-004
  ROLE: Verifies
- TYPE: Parent
  VALUE: IF-002
  ROLE: Verifies

[REQUIREMENT]
MID: mid_req_tst_007
UID: TST-007
TYPE: TestCase
STATUS: Approved
PRIORITY: High
VERIFICATION_METHOD: Test
OWNER: Инженер по испытаниям
SOURCE: ТЗ пилота, раздел 13
TAGS: тест, устаревшие-данные, HMI
TITLE: Проверка признака устаревших данных
STATEMENT: >>>
В 20 испытаниях прекратить поток телеметрии, дождаться фиксации потери связи,
наблюдать признак устаревших данных на HMI в течение 10 циклов обновления и затем
восстановить передачу корректных сообщений.
<<<
RATIONALE: >>>
Испытание проверяет появление, удержание и снятие признака устаревших данных во всём
сценарии потери и восстановления связи.
<<<
ACCEPTANCE_CRITERIA: >>>
Во всех 20 испытаниях признак появляется не позднее 2,0 секунды после фиксации
потери связи, остаётся видимым во всех 10 циклах без корректной телеметрии и
исчезает не позднее 2,0 секунды после первого нового корректного сообщения.
<<<
COMMENT: Добавлено в v2 для проверки SYS-006.
RELATIONS:
- TYPE: Parent
  VALUE: SYS-006
  ROLE: Verifies
