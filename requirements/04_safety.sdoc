[DOCUMENT]
MID: mid_doc_safety
TITLE: Требования безопасности
VERSION: 1.0
DATE: 2026-09-01
OPTIONS:
  ENABLE_MID: True

[GRAMMAR]
IMPORT_FROM_FILE: grammar.sgra

[REQUIREMENT]
MID: mid_req_saf_001
UID: SAF-001
TYPE: Safety
STATUS: Approved
PRIORITY: Critical
VERIFICATION_METHOD: Test
OWNER: Инженер по безопасности
SOURCE: ТЗ пилота, раздел 8
TAGS: безопасность, качество-данных, авария
TITLE: Недостоверные данные не снимают аварию
STATEMENT: >>>
Система не должна снимать зафиксированную аварию на основании значения давления,
помеченного как недостоверное.
<<<
RATIONALE: >>>
Использование недостоверных данных для снятия аварии способно скрыть сохраняющуюся
опасную ситуацию и создать ложное представление о нормальном режиме.
<<<
ACCEPTANCE_CRITERIA: >>>
Во всех испытаниях с активной аварией поступление значений с признаком недостоверности не
изменяет состояние аварии независимо от численного значения давления.
<<<
COMMENT: Базовое требование безопасности версии v1.
RELATIONS:
- TYPE: Parent
  VALUE: SYS-003
  ROLE: Derives
- TYPE: Parent
  VALUE: SYS-005
  ROLE: Derives

[REQUIREMENT]
MID: mid_req_saf_002
UID: SAF-002
TYPE: Safety
STATUS: Approved
PRIORITY: Critical
VERIFICATION_METHOD: Test
OWNER: Инженер по безопасности
SOURCE: ТЗ пилота, раздел 8
TAGS: безопасность, потеря-связи, фиксация
TITLE: Потеря связи формирует фиксируемую аварию
STATEMENT: >>>
Система должна формировать фиксируемую аварию при обнаружении потери связи с источником
телеметрии.
<<<
RATIONALE: >>>
Потеря наблюдаемости контролируемого процесса является самостоятельным опасным событием и
должна оставаться заметной до реакции оператора.
<<<
ACCEPTANCE_CRITERIA: >>>
В каждом из 20 испытаний потеря связи переводит систему в аварийное состояние, которое не
снимается восстановлением связи без явного подтверждения оператором.
<<<
COMMENT: Базовое требование безопасности версии v1.
RELATIONS:
- TYPE: Parent
  VALUE: SYS-005
  ROLE: Derives
